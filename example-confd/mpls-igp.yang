submodule mpls-igp {
  yang-version "1";
  belongs-to "mpls" {
    prefix "mpls";
  }
  // import some basic types
  import mpls-ldp { prefix ldp; }
  import mpls-sr { prefix sr; }
  // meta
  organization "OpenConfig working group";
  contact
    "OpenConfig working group
    netopenconfig@googlegroups.com";
  description
    "Configuration generic configuration parameters for IGP-congruent
    LSPs";
  revision "2014-07-07" {
    description
      "Initial revision";
    reference "TBD";
  }
  // extension statements
  // feature statements
  // identity statements
  // typedef statements
  // grouping statements
  grouping igp-lsp-common {
    description "common definitions for IGP-congruent LSPs";
    // container path-attributes {
    //  description "general path attribute settings for IGP-based
    //  LSPs";
    //}
  }
  grouping igp-lsp-setup {
    description "signaling protocol definitions for IGP-based LSPs";
    container path-setup-protocol {
      description "select and configure the signaling method for
          the LSP";
      // uses path-setup-common;
      uses ldp:igp-lsp-ldp-setup;
      uses sr:igp-lsp-sr-setup;
    }
  }
  // data definition statements
  // augment statements
  // rpc statements
  // notification statements
}
