module mpls-sr {
  yang-version "1";
  // namespace
  namespace "http://openconfig.net/yang/sr";
  prefix "sr";
  // import some basic types
  import ietf-inet-types { prefix inet; }
  import mpls-types { prefix mplst; }
  // meta
  organization "OpenConfig working group";
  contact
    "OpenConfig working group
    netopenconfig@googlegroups.com";
  description
    "Configuration for MPLS with segment routing-based LSPs,
    including global parameters, and LSP-specific configuration for
    both constrained-path and IGP-congruent LSPs";
  revision "2014-07-07" {
    description
      "Initial revision";
    reference "TBD";
  }
  // extension statements
  // feature statements
  // identity statements
  // typedef statements
  // grouping statements
  grouping sr-global {
    description "global segment routing signaling configuration";
    container segment-routing {
      description "SR global signaling config";
    }
  }
  grouping te-tunnel-sr {
    description "defintiions for SR-signaled LSP tunnel types,
    .e.g., applicable to point-to-point LSPs";
    container tunnel {
      description "contains configuration stanzas for different LSP
      tunnel types (P2P, P2MP, etc.)";
      leaf tunnel-type {
        type mplst:tunnel-type;
        description "specifies the type of LSP, e.g., P2P or P2MP";
      }
      container p2p-lsp {
        when "../tunnel-type = 'P2P'" {
          description "container active when LSP tunnel type is
          point to point";
        }
        description "Config for point-to-point tunnels";
        // fill out the configuration details per segment
        // routing requrements
      }
    }
  }
  grouping te-lsp-sr-setup {
    description "data definitions for SR signaling";
    container segment-routing {
      presence "Presence of this container sets the LSP to use
      SR signaling";
      description "Configuration for signaling SR-based TE LSPs";
      uses te-tunnel-sr;
    }
  }
  grouping igp-tunnel-sr {
    description "defintiions for SR-signaled, IGP-based LSP tunnel
    types";
    container tunnel {
      description "contains configuration stanzas for different LSP
      tunnel types (P2P, P2MP, etc.)";
      leaf tunnel-type {
        type mplst:tunnel-type;
        description "specifies the type of LSP, e.g., P2P or P2MP";
      }
      container p2p-lsp {
        when "../tunnel-type = 'P2P'" {
          description "container active when LSP tunnel type is
          point to point";
        }
        description "properties of point-to-point tunnels";
        leaf-list fec-address {
          type inet:ip-prefix;
          description "Address prefix for packets sharing the same
          forwarding equivalence class for the IGP-based LSP";
        }
      }
    }
  }
  grouping igp-lsp-sr-setup {
    description "grouping for SR-IGP path setup for IGP-congruent
    LSPs";
    container segment-routing {
      presence "Presence of this container sets the LSP to use
      SR signaling";
      description "segment routing signaling extensions for
      IGP-confgruent LSPs";
      uses igp-tunnel-sr;
    }
  }
  // data definition statements
  // augment statements
  // rpc statements
  // notification statements
}
