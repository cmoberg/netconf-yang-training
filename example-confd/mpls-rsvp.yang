module mpls-rsvp {
  yang-version "1";
  // namespace
  namespace "http://openconfig.net/yang/rsvp";
  prefix "rsvp";
  // import some basic types
  import ietf-inet-types { prefix inet; }
  import mpls-types { prefix mplst; }
  // meta
  organization "OpenConfig working group";
  contact
    "OpenConfig working group
    netopenconfig@googlegroups.com";
  description
    "Configuration for RSVP signaling, including global protocol
    parameters and LSP-specific configuration for constrained-path
    LSPs";
  revision "2014-07-07" {
    description
      "Initial revision";
    reference "TBD";
  }
  // extension statements
  // feature statements
  // identity statements
  // typedef statements
  // grouping statements
  grouping rsvp-global {
    description "Global RSVP protocol configuration";
    container rsvp {
      description "RSVP global signaling protocol configuration";
      // interfaces, bw percentages, hello timers, etc goes here";
      list interfaces {
        key interface-name;
        description "list of per-interface RSVP configurations";
        // TODO: update to interface ref -- move to separate
        // augmentation.
        leaf interface-name {
          type string;
          description "references a configured IP interface";
        }
        leaf hello-interval {
          type uint16 {
            range 0..60000;
          }
          units milliseconds;
          description "set the interval in ms between RSVP hello
          messages";
        }
        // TODO: confirm that the described semantics are supported
        // on various implementations. Finer grain configuration
        // will be vendor-specific
        leaf refresh-reduction {
          type boolean;
          default true;
          description "enables all RSVP refresh reduction message
          bundling, RSVP message ID, reliable message delivery
          and summary refresh";
          reference "RFC 2961 RSVP Refresh Overhead Reduction
          Extensions";
        }
        leaf refresh-reduction-reliable {
          type boolean;
          default true;
          description "enables RSVP refresh reduction reliable
          delivery and message_ID";
          reference "RFC 2961 RSVP Refresh Overhead Reduction
          Extensions";
        }
        leaf subscription {
          type mplst:percentage;
          description "percentage of the interface bandwidth that
          RSVP can reserve";
        }
        leaf ted-update-threshold {
          type mplst:percentage;
          description "percentage of interface bandwidth change
          that triggers an update event into the IGP TED";
        }
        // TODO: this may need to be moved to common TE LSP config
        container link-protection {
          description "link-protection (NHOP) related configuration";
          presence "presence of this container indicates facility
           protection is configured on the interface";
          leaf link-protection-only {
            type boolean;
            default false;
            description "disables node protection on this interface,
             and forces only link protection";
          }
          leaf bypass-optimize-interval {
            type uint16;
            units seconds;
            description "interval between periodic optimization
            of the bypass LSPs";
            // note: this is interface specific on juniper
            // on iox, this is global. need to resolve.
          }
        // to be completed, things like enabling link protection,
        // optimization times, etc.
        }
      }
      container soft-preemption {
        description "options relating to RSVP soft preemption";
        presence "presence of this container enables RSVP soft
          preemption on a node";
        leaf soft-preemption-timeout {
          type uint16 {
            range 0..300;
          }
          default 0;
          description "timeout value for soft preemption to revert
            to hard preemption";
        }
      }
    }
  }
  grouping te-tunnel-rsvp {
    description "defintiions for RSVP-signaled LSP tunnel types,
    .e.g., applicable to point-to-point LSPs";
    container tunnel {
      description "contains configuration stanzas for different LSP
      tunnel types (P2P, P2MP, etc.)";
      leaf tunnel-type {
        type mplst:tunnel-type;
        description "specifies the type of LSP, e.g., P2P or P2MP";
      }
      container p2p-lsp {
        when "../tunnel-type = 'P2P'" {
          description "container active when LSP tunnel type is
          point to point";
        }
        description "properties of point-to-point tunnels";
        leaf destination {
          type inet:ip-address;
          description "destination egress node for the LSP";
        }
        leaf tunnel-local-id {
          type union {
            type uint32;
            type string;
          }
          description "locally signficant optional identifier for the
          LSP; may be a numerical or string value";
        }
        leaf soft-preemption {
          type boolean;
          description "enables RSVP soft-preemption on this LSP";
          default false;
        }
      } // p2p-lsp
      container p2mp-lsp {
        when "../tunnel-type = 'P2MP'" {
          description "container is active when LSP tunnel type is
          point to multipoint";
        }
        description "properties of point-to-multipoint tunnels";
        leaf-list destination {
          type inet:ip-address;
          description "list of destinations / egress nodes for the
          multipoint LSP tunnel";
        }
      }
    }
  }
  grouping te-lsp-rsvp-setup {
    description "data definitions for RSVP-signalled LSPs";
    container rsvp {
      presence "Presence of this container sets the LSP to use
      RSVP signaling";
      description "Configuration for RSVP-signalled TE LSPs";
      container path-specification {
        description "Definition of primary/backup paths for purpose
        of signaling the LSP";
      }
      leaf setup-priority {
        type uint8 {
          range 0..7;
        }
        default 7;
        description "preemption priority during LSP setup, lower is
        higher priority; default 7 indicates that LSP will not
        preempt established LSPs during setup";
      }
      leaf hold-priority {
        type uint8 {
          range 0..7;
        }
        default 0;
        description "preemption priority once the LSP is established,
        lower is higher priority; default 0 indicates that other LSPs
        will not preempt the LSPs once established";
      }
      leaf retry-timer {
        type uint16 {
          range 1..600;
        }
        units seconds;
        description "sets the time between attempts to establish the
        LSP";
      }
      //TODO: add other RSPV parms: optimize delay, switchover delay,
      // etc.
      // include tunnel (p2p, p2mp, etc).
      uses te-tunnel-rsvp;
    }
  }
  // data definition statements
  // augment statements
  // rpc statements
  // notification statements
}
